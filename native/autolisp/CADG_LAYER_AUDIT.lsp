(defun c:CADG_QS_AUDIT (/ layers textSelection count)
  (setq layers (tblsearch "LAYER" "0"))
  (setq textSelection (ssget "X" '((0 . "TEXT,MTEXT"))))
  (setq count (if textSelection (sslength textSelection) 0))
  (princ (strcat "\nCAD Guardian quick-start audit"))
  (princ (strcat "\nLayer 0 exists: " (if layers "yes" "no")))
  (princ (strcat "\nText-like entities found: " (itoa count)))
  (if (> count 0)
    (progn
      (setq entityData (entget (ssname textSelection 0)))
      (princ (strcat "\nFirst text entity type: " (cdr (assoc 0 entityData))))
    )
  )
  (command "_.REGEN")
  (princ)
)
